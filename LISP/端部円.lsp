(defun c:lc ()
  (progn (setq sc (getreal "Scale:")))
  (setq location (getpoint "\ncoordinate:"))
  (setq location2 (getpoint "\ncoordinate:"))
  (command "_pline" location location2 "")
  (command "_circle" location sc)
  (command "_circle" location2 sc)
  (princ)
)
